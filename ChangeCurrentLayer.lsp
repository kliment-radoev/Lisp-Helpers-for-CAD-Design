;CHANGE CURRENT LAYER;

(defun C:`1 () (setvar "clayer" "Zz00Spec")(princ)); END OF DEFUN 12
(defun C:112 () (setvar "clayer" "Zz010")(princ)); END OF DEFUN 11
(defun C:12 () (setvar "clayer" "Zz015")(princ)); END OF DEFUN 12
(defun C:23 () (setvar "clayer" "Zz020")(princ)); END OF DEFUN 23
(defun C:223 () (setvar "clayer" "Zz025")(princ)); END OF DEFUN 223
(defun C:34 () (setvar "clayer" "Zz030")(princ)); END OF DEFUN 34
(defun C:45 () (setvar "clayer" "Zz040")(princ)); END OF DEFUN 45
(defun C:56 () (setvar "clayer" "Zz050")(princ)); END OF DEFUN 56
(defun C:67 () (setvar "clayer" "Zz060")(princ)); END OF DEFUN 67
(defun C:78 () (setvar "clayer" "Zz070")(princ)); END OF DEFUN 78
(defun C:89 () (setvar "clayer" "Zz080")(princ)); END OF DEFUN 89
(defun C:90 () (setvar "clayer" "Zz00Dim")(princ)); END OF DEFUN 90
(defun C:0- () (setvar "clayer" "0")(princ)); END OF DEFUN 0-
(defun C:-= () (setvar "clayer" "Zz00Hatch")(princ)); END OF DEFUN -=
                    ;-hatch layers;
(defun C:S`1 () (setvar "clayer" "ZzS000")(princ)); END OF DEFUN S12
(defun C:S12 () (setvar "clayer" "ZzS010")(princ)); END OF DEFUN S12
(defun C:S23 () (setvar "clayer" "ZzS020")(princ)); END OF DEFUN S23
(defun C:S34 () (setvar "clayer" "ZzS030")(princ)); END OF DEFUN S34
(defun C:S23 () (setvar "clayer" "ZzS040")(princ)); END OF DEFUN S45
(defun C:S34 () (setvar "clayer" "ZzS050")(princ)); END OF DEFUN S56
