;OFF SPESIFIED LAYER;
(defun C:F` () 
(setq ww (getvar "clayer")) 
(if (= ww "ZZ00Spec") 
(princ "\n Cannot off the current layer !!!") 
(command "_.-layer" "_off" "Zz00Spec" ""))
(princ)
)

(defun C:F11 () 
(setq ww (getvar "clayer")) 
(if (= ww "ZZ010") 
(princ "\n Cannot off the current layer !!!") 
(command "_.-layer" "_off" "Zz010" "")) 
(princ)
)

(defun C:F1 () 
(setq ww (getvar "clayer")) 
(if (= ww "ZZ015") 
(princ "\n Cannot off the current layer !!!") 
(command "_.-layer" "_off" "Zz015" "")) 
(princ)
)

(defun C:F2 () 
(setq ww (getvar "clayer")) 
(if (= ww "ZZ020") 
(princ "\n Cannot off the current layer !!!") 
(command "_.-layer" "_off" "Zz020" "")) 
(princ)
)

(defun C:F22 () 
(setq ww (getvar "clayer")) 
(if (= ww "ZZ025") 
(princ "\n Cannot off the current layer !!!") 
(command "_.-layer" "_off" "Zz025" "")) 
(princ)
)

(defun C:F3 () 
(setq ww (getvar "clayer")) 
(if (= ww "ZZ030") 
(princ "\n Cannot off the current layer !!!") 
(command "_.-layer" "_off" "Zz030" "")) 
(princ)
)

(defun C:F4 () 
(setq ww (getvar "clayer")) 
(if (= ww "ZZ040") 
(princ "\n Cannot off the current layer !!!") 
(command "_.-layer" "_off" "Zz040" "")) 
(princ)
)

(defun C:F5 () 
(setq ww (getvar "clayer")) 
(if (= ww "ZZ050") 
(princ "\n Cannot off the current layer !!!") 
(command "_.-layer" "_off" "Zz050" "")) 
(princ)
)

(defun C:F6 () 
(setq ww (getvar "clayer")) 
(if (= ww "ZZ060") 
(princ "\n Cannot off the current layer !!!") 
(command "_.-layer" "_off" "Zz060" "")) 
(princ)
)

(defun C:F7 () 
(setq ww (getvar "clayer")) 
(if (= ww "ZZ070") 
(princ "\n Cannot off the current layer !!!") 
(command "_.-layer" "_off" "Zz070" "")) 
(princ)
)

(defun C:F8 () 
(setq ww (getvar "clayer")) 
(if (= ww "ZZ080") 
(princ "\n Cannot off the current layer !!!") 
(command "_.-layer" "_off" "Zz080" "")) 
(princ)
)

(defun C:F9 () 
(setq ww (getvar "clayer")) 
(if (= ww "ZZ00Dim") 
(princ "\n Cannot off the current layer !!!") 
(command "_.-layer" "_off" "ZZ00Dim" "")) 
(princ)
)

(defun C:F0 () 
(setq ww (getvar "clayer")) 
(if (= ww "0") 
(princ "\n Cannot off the current layer !!!") 
(command "_.-layer" "_off" "0" "")) 
(princ)
)

(defun C:F- () 
(setq ww (getvar "clayer")) 
(if (= ww "ZZ00Hatch") 
(princ "\n Cannot off the current layer !!!") 
(command "_.-layer" "_off" "ZZ00Hatch" "")) 
(princ)
)

                     ;-hatch layers;

(defun C:FS` () 
(setq ww (getvar "clayer")) 
(if (= ww "ZZS000") 
(princ "\n Cannot off the current layer !!!") 
(command "_.-layer" "_off" "ZzS000" "")) 
(princ)
)

(defun C:FS1 () 
(setq ww (getvar "clayer")) 
(if (= ww "ZZS010") 
(princ "\n Cannot off the current layer !!!") 
(command "_.-layer" "_off" "ZzS010" "")) 
(princ)
)

(defun C:FS2 () 
(setq ww (getvar "clayer")) 
(if (= ww "ZZS020") 
(princ "\n Cannot off the current layer !!!") 
(command "_.-layer" "_off" "ZzS020" "")) 
(princ)
)

(defun C:FS3 () 
(setq ww (getvar "clayer")) 
(if (= ww "ZZS030") 
(princ "\n Cannot off the current layer !!!") 
(command "_.-layer" "_off" "ZzS030" "")) 
(princ)
)

(defun C:FS4 () 
(setq ww (getvar "clayer")) 
(if (= ww "ZZS040") 
(princ "\n Cannot off the current layer !!!") 
(command "_.-layer" "_off" "ZzS040" "")) 
(princ)
)

(defun C:FS5 () 
(setq ww (getvar "clayer")) 
(if (= ww "ZZS050") 
(princ "\n Cannot off the current layer !!!") 
(command "_.-layer" "_off" "ZzS050" "")) 
(princ)
)
