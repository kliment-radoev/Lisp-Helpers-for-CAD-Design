;ON SPECIFIED LAYER;

(defun C:OO ()
(command "_.layon" "")
(princ)
)

(defun C:O` () 
(command "_.-layer" "_on" "Zz00Spec" "")
(princ)
)

(defun C:O11 () 
(command "_.-layer" "_on" "Zz010" "")
(princ)
)

(defun C:O1 () 
(command "_.-layer" "_on" "Zz015" "")
(princ)
)

(defun C:O2 () 
(command "_.-layer" "_on" "Zz020" "")
(princ)
)

(defun C:O22 () 
(command "_.-layer" "_on" "Zz025" "")
(princ)
)

(defun C:O3 () 
(command "_.-layer" "_on" "Zz030" "")
(princ)
)

(defun C:O4 () 
(command "_.-layer" "_on" "Zz040" "")
(princ)
)

(defun C:O5 () 
(command "_.-layer" "_on" "Zz050" "")
(princ)
)

(defun C:O6 () 
(command "_.-layer" "_on" "Zz060" "")
(princ)
)

(defun C:O7 () 
(command "_.-layer" "_on" "Zz070" "")
(princ)
)

(defun C:O8 () 
(command "_.-layer" "_on" "Zz080" "")
(princ)
)

(defun C:O9 () 
(command "_.-layer" "_on" "Zz00Dim" "")
(princ)
)

(defun C:O0 () 
(command "_.-layer" "_on" "0" "")
(princ)
)

(defun C:O- () 
(command "_.-layer" "_on" "Zz00Hatch" "")
(princ)
)
                    ;-hatch layers;
(defun C:OS` () 
(command "_.-layer" "_on" "ZzS000" "")
(princ)
)

(defun C:OS1 () 
(command "_.-layer" "_on" "ZzS010" "")
(princ)
)

(defun C:OS2 () 
(command "_.-layer" "_on" "ZzS020" "")
(princ)
)

(defun C:OS3 () 
(command "_.-layer" "_on" "ZzS030" "")
(princ)
)

(defun C:OS4 () 
(command "_.-layer" "_on" "ZzS040" "")
(princ)
)

(defun C:OS5 () 
(command "_.-layer" "_on" "ZzS060" "")
(princ)
)
