;THAW SPESIFIED LAYER;

(defun C:T` () 
(command "_.-layer" "_thaw" "Zz00Spec" "")
(princ)
)

(defun C:T11 () 
(command "_.-layer" "_thaw" "Zz010" "")
(princ)
)

(defun C:T1 () 
(command "_.-layer" "_thaw" "Zz015" "")
(princ)
)

(defun C:T2 () 
(command "_.-layer" "_thaw" "Zz020" "")
(princ)
)

(defun C:T22 () 
(command "_.-layer" "_thaw" "Zz025" "")
(princ)
)

(defun C:T3 () 
(command "_.-layer" "_thaw" "Zz030" "")
(princ)
)

(defun C:T4 () 
(command "_.-layer" "_thaw" "Zz040" "")
(princ)
)

(defun C:T5 () 
(command "_.-layer" "_thaw" "Zz050" "")
(princ)
)

(defun C:T6 () 
(command "_.-layer" "_thaw" "Zz060" "")
(princ)
)

(defun C:T7 () 
(command "_.-layer" "_thaw" "Zz070" "")
(princ)
)

(defun C:T8 () 
(command "_.-layer" "_thaw" "Zz080" "")
(princ)
)

(defun C:T9 () 
(command "_.-layer" "_thaw" "Zz00Dim" "")
(princ)
)

(defun C:T0 () 
(command "_.-layer" "_thaw" "0" "")
(princ)
)

(defun C:T- () 
(command "_.-layer" "_thaw" "Zz00Hatch" "")
(princ)
)

                    ;-hatch layers;

(defun C:TS` () 
(command "_.-layer" "_thaw" "ZzS000" "")
(princ)
)

(defun C:TS1 () 
(command "_.-layer" "_thaw" "ZzS010" "")
(princ)
)

(defun C:TS2 () 
(command "_.-layer" "_thaw" "ZzS020" "")
(princ)
)

(defun C:TS3 () 
(command "_.-layer" "_thaw" "ZzS030" "")
(princ)
)

(defun C:TS4 () 
(command "_.-layer" "_thaw" "ZzS040" "")
(princ)
)

(defun C:TS5 () 
(command "_.-layer" "_thaw" "ZzS050" "")
(princ)
)
